__title__ = "laser cut box"
__author__ = "Greg Harley"
__version__ = "01.00"
__date__ = "12/31/20"

__Comment__ = "This macro creates a sketch of a laser cut box which can then be save to a DXF file."

from enum import Enum
from typing import Optional

from PySide import QtCore, QtGui, QtSvg
from FreeCAD import Gui
import Part, PartDesign, Sketcher

App = FreeCAD

# Indexes for geoid
START = 1
END = 2
ORIGIN = -1

# Indexes for box sides
TOP = 0
RIGHT = 1
BOTTOM = 2
LEFT = 3


# Box type enums
class BoxType(Enum):
    All = 0
    SLOTS = 1
    TABS = 2


# Directional enums for drawing edges
class Direction(Enum):
    EAST = 1
    SOUTH = 2
    WEST = 3
    NORTH = 4


# DotDict - easy dictionary access
class DotDict(dict):
    """dot.notation access to dictionary attributes"""
    __getattr__ = dict.get
    __setattr__ = dict.__setitem__
    __delattr__ = dict.__delitem__


# Face enums for drawing edges
class Face(Enum):
    SIDE = 1
    END = 2
    BOTTOM = 3


class Box:
    def __init__(self):
        if not App.ActiveDocument:
            App.newDocument()

        self.macro_dir = App.getUserMacroDir()

        self.dialog = Optional[QtGui.QWidget]
        self.image = Optional[QtGui.QLabel]
        self.widget = Optional[QtSvg.QSvgWidget]

        self.worksheet = None
        self.props = DotDict()
        self.constrain = False
        self.box_type = BoxType.All

        self._init_dialog()

        self.dialog.show()
        self._update_image(0)
        self.dialog.exec_()

    def _update_image(self, box_type):
        if not isinstance(self.widget, QtSvg.QSvgWidget):
            self.widget = QtSvg.QSvgWidget(self.dialog)
            self.widget.setGeometry(self.image.geometry())

        if box_type == BoxType.All:
            self.widget.renderer().load(self.macro_dir + 'end_all.svg')
        elif box_type == BoxType.SLOTS:
            self.widget.renderer().load(self.macro_dir + 'end_slots.svg')
        else:
            self.widget.renderer().load(self.macro_dir + 'end_edge.svg')

        self.widget.show()

    def _init_dialog(self):
        self.dialog = Gui.PySideUic.loadUi('{0}Macro_LaserCutBox.ui'.format(self.macro_dir))
        self.dialog.setWindowTitle("Laser cut box")
        self.image = self.dialog.findChild(QtGui.QLabel, 'image')

        QtCore.QObject.connect(self.dialog.buttonBox, QtCore.SIGNAL('accepted()'), self.build_geometry)
        QtCore.QObject.connect(self.dialog.tabTypes, QtCore.SIGNAL('currentIndexChanged(int)'), self._update_image)

    def _init_properties(self):
        for obj in self.dialog.findChildren(QtGui.QLabel):
            buddy = obj.buddy()
            if buddy is not None:
                buddy_name = buddy.objectName()

                if isinstance(buddy, QtGui.QComboBox):
                    self.box_type = buddy.currentIndex()
                else:
                    self.props[buddy_name] = int(buddy.text()) if buddy_name.startswith('num') else float(buddy.text())

        if self.props.depth == 0:
            self.props.depth = self.props.width

        if self.props.bottomThickness == 0:
            self.props.bottomThickness = self.props.thickness

        if self.props.lidThickness == 0:
            self.props.lidThickness = self.props.thickness

        if self.props.numTabsDepth == 0:
            self.props.numTabsDepth = self.props.numTabsWidth

        self.props.sideGap = float((self.props.width - self.props.numTabsWidth * self.props.tabWidth) / (self.props.numTabsWidth + 1))
        self.props.endGap = float((self.props.depth - self.props.numTabsDepth * self.props.tabWidth) / (self.props.numTabsDepth + 1))
        self.props.heightGap = float((self.props.height - self.props.numTabsHeight * self.props.tabWidth) / (self.props.numTabsHeight + 1))

    def build_geometry(self):
        self._init_properties()

        if self.dialog.chkSide.isChecked():
            self.build_long_side()

        if self.dialog.chkEnd.isChecked():
            self.build_short_side()

        if self.dialog.chkBottom.isChecked():
            self.build_bottom()

    def _build_side(self, sketch_name, face, tab_func):
        sketch = self._add_sketch(sketch_name)

        thickness = self.props.thickness

        if face is Face.SIDE:
            width = self.props.width
        elif face is Face.END:
            width = self.props.depth
        else:
            width = 0

        actual_width = width + thickness
        height = self.props.height

        bottom_thickness = self.props.bottomThickness
        lid_thickness = self.props.lidThickness

        if self.box_type == BoxType.All:
            actual_height = height + lid_thickness + bottom_thickness * 2
        elif self.box_type == BoxType.SLOTS:
            actual_height = height + lid_thickness + bottom_thickness
        else:
            actual_height = height + bottom_thickness

        lower_left, upper_left, lower_right, upper_right = self.get_vectors(actual_width, actual_height)

        box = [[sketch.addGeometry(Part.LineSegment(upper_left, upper_right), False)]]

        lines = self.draw_edge_tabs(sketch, face, Direction.EAST, True, actual_height, lower_right)
        box.append(lines)

        if self.box_type != BoxType.SLOTS:
            lines = self.draw_edge_tabs(sketch, face, Direction.SOUTH, True, actual_width, lower_left)
        else:
            lines = [sketch.addGeometry(Part.LineSegment(lower_left, lower_right), False)]

        box.append(lines)

        lines = self.draw_edge_tabs(sketch, face, Direction.WEST, False, actual_height, lower_left)
        box.append(lines)

        if self.constrain:
            self._constrain_sides(sketch, box)

            sketch.addConstraint(Sketcher.Constraint('Horizontal', box[TOP][0]))
            sketch.addConstraint(Sketcher.Constraint('DistanceX', box[TOP][0], actual_width))
            sketch.addConstraint(Sketcher.Constraint('DistanceY', box[LEFT][0], START, box[LEFT][-1], END, -actual_height))

            if self.box_type == BoxType.SLOTS:
                sketch.addConstraint(Sketcher.Constraint('DistanceY', box[RIGHT][0], START, box[RIGHT][-1], END, -actual_height))

            sketch.addConstraint(Sketcher.Constraint('Symmetric', box[TOP][0], START, box[RIGHT][-1], END, ORIGIN, START))

        if self.box_type != BoxType.TABS:
            tab = tab_func(sketch, actual_height)

            if self.constrain:
                sketch.addConstraint(Sketcher.Constraint('DistanceX', box[TOP][0], START, tab[TOP][0], START, self.props.sideGap if face is Face.SIDE else self.props.endGap))
                sketch.addConstraint(Sketcher.Constraint('DistanceY', tab[TOP][0], START, box[TOP][0], START, lid_thickness))

        App.ActiveDocument.recompute(None, True, True)
        Gui.ActiveDocument.ActiveView.fitAll()

    def build_bottom(self):
        sketch = self._add_sketch('BoxBottom')

        width = self.props.width
        depth = self.props.depth

        lower_left, upper_left, lower_right, upper_right = self.get_vectors(width, depth)

        box = [self.draw_edge_tabs(sketch, Face.BOTTOM, Direction.NORTH, False, width, upper_left),
               self.draw_edge_tabs(sketch, Face.BOTTOM, Direction.EAST, False, depth, lower_right),
               self.draw_edge_tabs(sketch, Face.BOTTOM, Direction.SOUTH, False, width, lower_left),
               self.draw_edge_tabs(sketch, Face.BOTTOM, Direction.WEST, False, depth, lower_left)]

        if self.constrain:
            self._constrain_sides(sketch, box)

            sketch.addConstraint(Sketcher.Constraint('DistanceX', box[TOP][0], START, box[TOP][-1], END, width))
            sketch.addConstraint(Sketcher.Constraint('DistanceY', box[LEFT][0], START, box[LEFT][-1], END, -depth))
            sketch.addConstraint(Sketcher.Constraint('Symmetric', box[TOP][0], START, box[RIGHT][-1], END, ORIGIN, START))

        App.ActiveDocument.recompute(None, True, True)
        Gui.ActiveDocument.ActiveView.fitAll()

    def build_long_side(self):
        self._build_side('BoxSide', Face.SIDE, self.draw_side_slots)

    def build_short_side(self):
        self._build_side('BoxEnd', Face.END, self.draw_end_slots)

    def draw_slot(self, sketch, width, height, offset):
        lower_left, upper_left, lower_right, upper_right = self.get_vectors(width, height)

        top = sketch.addGeometry(Part.LineSegment(upper_left + offset, upper_right + offset), False)
        right = sketch.addGeometry(Part.LineSegment(lower_right + offset, upper_right + offset), False)
        bottom = sketch.addGeometry(Part.LineSegment(lower_left + offset, lower_right + offset), False)
        left = sketch.addGeometry(Part.LineSegment(lower_left + offset, upper_left + offset), False)

        if self.constrain:
            sketch.addConstraint(Sketcher.Constraint('Horizontal', top))
            sketch.addConstraint(Sketcher.Constraint('Vertical', left))
            sketch.addConstraint(Sketcher.Constraint('Vertical', right))

            sketch.addConstraint(Sketcher.Constraint('Equal', left, right))

            sketch.addConstraint(Sketcher.Constraint('DistanceX', top, width))
            sketch.addConstraint(Sketcher.Constraint('DistanceY', left, height))

            sketch.addConstraint(Sketcher.Constraint('Coincident', top, END, right, START))
            sketch.addConstraint(Sketcher.Constraint('Coincident', right, END, bottom, START))
            sketch.addConstraint(Sketcher.Constraint('Coincident', bottom, END, left, START))
            sketch.addConstraint(Sketcher.Constraint('Coincident', left, END, top, START))

        return [top, right, bottom, left]

    def _draw_slots(self, sketch, num_tabs, gap, start):
        tabs = []
        first = []
        tab_width = self.props.tabWidth
        bottom_thickness = self.props.bottomThickness

        for idx in range(0, num_tabs):
            tab = self.draw_slot(sketch, tab_width, bottom_thickness, start + App.Vector((tab_width + gap) * idx, 0))
            tabs.append(tab)

            if idx == 0:
                first = tab
            elif self.constrain:
                sketch.addConstraint(Sketcher.Constraint('DistanceX', first[TOP], END, tab[TOP], START, gap * idx + tab_width * (idx - 1)))
                sketch.addConstraint(Sketcher.Constraint('DistanceY', first[TOP], END, tab[TOP], START, 0))

        return tabs

    def draw_end_slots(self, sketch, height):
        start = App.Vector(self.props.endGap, height - self.props.lidThickness - self.props.bottomThickness)
        return self._draw_slots(sketch, self.props.numTabsDepth, self.props.endGap, start)

    def draw_side_slots(self, sketch, height):
        start = App.Vector(self.props.sideGap, height - self.props.lidThickness - self.props.bottomThickness)
        return self._draw_slots(sketch, self.props.numTabsWidth, self.props.sideGap, start)

    def draw_edge_tabs(self, sketch, face, direction, is_inset, length, start):
        is_vertical = direction is Direction.EAST or direction is Direction.WEST
        config = DotDict()
        config.tabWidth = self.props.tabWidth

        lines = []

        def add_line(start_point, end_offset, previous):
            end_point = start_point + end_offset
            new_line = Part.LineSegment(start_point, end_point)
            new_index = sketch.addGeometry(new_line, False)

            if self.constrain and previous != -1:
                sketch.addConstraint(Sketcher.Constraint('Coincident', previous, END, new_index, START))
                sketch.addConstraint(Sketcher.Constraint('Perpendicular', previous, new_index))

            lines.append(new_index)

            return new_index, new_line

        if is_vertical:
            if face is Face.BOTTOM:
                config.numTabs = self.props.numTabsDepth
                config.gap = self.props.endGap
            else:
                config.numTabs = self.props.numTabsHeight
                config.gap = self.props.heightGap

            config.thickness = self.props.thickness

            if (is_inset and direction == Direction.EAST) or (not is_inset and direction == Direction.WEST):
                config.thickness = -config.thickness
        else:
            if face is Face.SIDE or face is Face.BOTTOM:
                config.numTabs = self.props.numTabsWidth
                config.gap = self.props.sideGap
            else:
                config.numTabs = self.props.numTabsDepth
                config.gap = self.props.endGap

            if face is Face.BOTTOM:
                config.thickness = self.props.thickness
            else:
                config.thickness = self.props.bottomThickness

            if (is_inset and direction == Direction.NORTH) or (not is_inset and direction == Direction.SOUTH):
                config.thickness = -config.thickness

        config.longOffset = (length - config.numTabs * config.tabWidth - config.gap * (config.numTabs - 1)) / 2.0

        if is_vertical:
            first_offset = last_offset = App.Vector(0, config.longOffset)
            gap_length = App.Vector(0, config.gap)
            tab_length = App.Vector(0, config.tabWidth)
            thickness_length = App.Vector(config.thickness, 0)
        else:
            if face is Face.BOTTOM:
                first_offset = last_offset = App.Vector(config.longOffset, 0)
            else:
                offset = App.Vector(config.thickness / 2, 0)
                first_offset = App.Vector(config.longOffset, 0) - offset
                last_offset = App.Vector(config.longOffset, 0) + offset

            gap_length = App.Vector(config.gap, 0)
            tab_length = App.Vector(config.tabWidth, 0)
            thickness_length = App.Vector(0, config.thickness)

        gap_line_index = -1
        first_tab_index = -1
        offset_line_index = -1
        thickness_line_index = -1
        line_index = -1
        line = Optional[Part.LineSegment]

        for idx in range(0, int(config.numTabs)):
            if idx == 0:
                line_index, line = add_line(start, first_offset, line_index)

                offset_line_index = line_index

                if self.constrain:
                    if is_vertical:
                        sketch.addConstraint(Sketcher.Constraint('Vertical', offset_line_index))
                    else:
                        sketch.addConstraint(Sketcher.Constraint('Horizontal', offset_line_index))
            else:
                line_index, line = add_line(line.EndPoint, gap_length, line_index)

                if gap_line_index == -1:
                    gap_line_index = line_index

                    if self.constrain:
                        constraint_type = 'DistanceY' if is_vertical else 'DistanceX'
                        sketch.addConstraint(Sketcher.Constraint(constraint_type, gap_line_index, config.gap))
                elif self.constrain:
                    sketch.addConstraint(Sketcher.Constraint('Equal', gap_line_index, line_index))

            line_index, line = add_line(line.EndPoint, thickness_length, line_index)

            if idx == 0:
                thickness_line_index = line_index

                if self.constrain:
                    constraint_type = 'DistanceX' if is_vertical else 'DistanceY'
                    sketch.addConstraint(Sketcher.Constraint(constraint_type, thickness_line_index, config.thickness))
            elif self.constrain:
                sketch.addConstraint(Sketcher.Constraint('Equal', thickness_line_index, line_index))

            line_index, line = add_line(line.EndPoint, tab_length, line_index)

            if idx == 0:
                first_tab_index = line_index

                if self.constrain:
                    constraint_type = 'DistanceY' if is_vertical else 'DistanceX'
                    sketch.addConstraint(Sketcher.Constraint(constraint_type, first_tab_index, config.tabWidth))
            elif self.constrain:
                sketch.addConstraint(Sketcher.Constraint('Equal', first_tab_index, line_index))

            line_index, line = add_line(line.EndPoint, -thickness_length, line_index)
            sketch.addConstraint(Sketcher.Constraint('Equal', thickness_line_index, line_index))

        add_line(line.EndPoint, last_offset, line_index)

        if self.constrain:
            constraint_type = 'DistanceY' if is_vertical else 'DistanceX'
            sketch.addConstraint(Sketcher.Constraint(constraint_type, offset_line_index, config.longOffset))

        return lines

    # Helper methods
    def get_sheet_expression_prefix(self):
        return '<<' + self.worksheet.Name + '>>.'

    @staticmethod
    def _add_sketch(sketch_name):
        body = App.ActiveDocument.addObject('PartDesign::Body', sketch_name)
        sketch = App.ActiveDocument.addObject('Sketcher::SketchObject', sketch_name + 'Sketch')
        body.addObject(sketch)

        return sketch

    @staticmethod
    def _constrain_sides(sketch, box):
        sketch.addConstraint(Sketcher.Constraint('Coincident', box[TOP][0], START, box[LEFT][0], START))
        sketch.addConstraint(Sketcher.Constraint('Coincident', box[BOTTOM][-1], END, box[RIGHT][-1], END))
        sketch.addConstraint(Sketcher.Constraint('Coincident', box[TOP][-1], END, box[RIGHT][0], START))
        sketch.addConstraint(Sketcher.Constraint('Coincident', box[BOTTOM][0], START, box[LEFT][-1], END))

    @staticmethod
    def get_line_length(sketch, line_array, is_vertical):
        start_line = sketch.Geometry[line_array[0]]
        end_line = sketch.Geometry[line_array[-1]]

        if is_vertical:
            length = end_line.EndPoint.y - start_line.StartPoint.y
        else:
            length = end_line.EndPoint.x - start_line.StartPoint.x

        return length

    @staticmethod
    def get_vectors(width, height):
        lower_left = App.Vector(0, 0, 0)
        upper_left = App.Vector(0, height, 0)
        lower_right = App.Vector(width, 0, 0)
        upper_right = App.Vector(width, height, 0)

        return lower_left, upper_left, lower_right, upper_right

    @staticmethod
    def log(message):
        App.Console.PrintMessage(str(message) + '\n')


Box()
